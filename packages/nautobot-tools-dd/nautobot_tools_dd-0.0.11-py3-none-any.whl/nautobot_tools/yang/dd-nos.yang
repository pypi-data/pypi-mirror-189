module dd-nos {
  yang-version 1.1;
  namespace "https://dataductus.com/nautobot/nos";
  prefix nos;

  organization "Data Ductus";

  description
    "Nautobot Object Scanner (NOS) .";

  revision 2022-11-22 {
    description
      "Initial development, prove of concept.";
  }

  container device {
    presence;
    leaf id {
      type string;
    }
    leaf name {
      type string;
    }
  }
 }
